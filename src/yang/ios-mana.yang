module ios-mana {
  namespace "http://com/example/ios-mana";
  prefix ios-mana;

  import ietf-inet-types {
    prefix inet;
  }
  import tailf-ncs {
    prefix ncs;
  }

  list ios-mana {
    key name;

    uses ncs:service-data;
    ncs:servicepoint "ios-mana";

    leaf name {
      type string;
    }

    // may replace this with other ways of refering to the devices.
    leaf-list device {
      type leafref {
        path "/ncs:devices/ncs:device/ncs:name";
      }
    }

    // replace with your own stuff here
    leaf rocommunity {
      type string;
      default "rocommunity";
    }

    leaf rwcommunity {
      type string;
      default "rwcommunity";
    }
    leaf server {
      mandatory true;
      type inet:ipv4-address;
    }
    leaf ntpserver {
      mandatory true;
      type inet:ipv4-address;

    }
    }
 }
